DeviceIdentity
--    { iso org(3) dod(6) internet(1) private(4) enterprise(1) twsided(46690) huffer(8) toluene(1) identity(1) }
    DEFINITIONS ::=
BEGIN

-- ECC signature, based on X9.64, containing (r, s). The algorithm and the
-- type of key are pre-negotiated based on the use case.
Signature ::= SEQUENCE {
    -- Signature r
    r INTEGER,

    -- Signature s
    s INTEGER
}

-- Contains the actual device identity information that is to be used
-- in managing and connecting to the target.
DeviceIdentityInfo ::= SEQUENCE {
    -- The ESSID we are to connect to
    wifiESSID UTF8String,

    -- The username for the network. Used only if using an EAP mode.
    wifiUsername UTF8String,

    -- The password for the network
    wifiPassword UTF8String,

    -- The type of authentication to use
    wifiAuthType UTF8String,

    -- The certificate to use, if any, for the desired auth mechanism
    wifiAuthCert OCTET STRING,

    -- The target host IP address or hostname to connect to
    targetHost UTF8String,

    -- The target port, TCP connections using TLS
    targetPort INTEGER,

    -- Our unique device identifier
    deviceId INTEGER,

    -- The server's CA root certificate, used to identify the host we're connecting to
    serverCaRoot OCTET STRING,

    -- The identity certificate chain for this device. This is an array of certificates,
    -- the first being the certificate representing the device, all the way up to the
    -- root. The root must match one of the trusted roots for the device.
    -- Optional for now.
    identityCertChain SEQUENCE OF OCTET STRING
}

-- A signed bundle containing all the important identity information for this device
DeviceIdentityBundle ::= SEQUENCE {
    -- This device's identity info, this will be decoded separately
    identityInfo DeviceIdentityInfo,
    -- Signature, from a trusted authority, for this device's identity information
    identityInfoSignature Signature
}

END
